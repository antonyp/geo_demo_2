FME workspace parcel-geojson2kml.fmw

Parameters:
- SourceDataset_GEOJSON = /Users/andrewharvey/github/geo-demos/demos/iag/src/data/sample.json   # Source GeoJSON File or URL
- DestDataset_OGCKML = /Users/andrewharvey/github/geo-demos/demos/iag/src/data/sample.kml   # Destination Google Earth KML File

Readers:
- GEOJSON_1: GEOJSON from $(SourceDataset_GEOJSON)

Writers:
- OGCKML_1: OGCKML to $(DestDataset_OGCKML)

Sample (reader GEOJSON_1)
    attributes: NM_POLH string, CDTYPRDH string, CDTYPRDD string, YearOfConstruction int, Number_of_Dwellings int, SizeOfDwlling int, SizeOfGarage int, AgeOfOldestPolicyHolder string, BuildingSumInsured string, ContentsSumInsured string, AtRiskOfFlood string, ThisYearBldgPremium string, ThisYearContPremium string, ThisYearSpecItemPremium string, Last5YearsBldgPremium float, NumberBuildingsTerms int, Last5YearsContPremium float, NumberContentsTerms int, AM_DUE_SPTM_5 int, LastDiasterClaim string, RecentBuildingClaim int, RecentContentsClaim int, RecentBuildingClaimCost float, RecentContentsClaimCost float, FiveYearBuildingClaim int, FiveYearContentsClaim int, FiveYearBuildingClaimCost float, FiveYearContentsClaimCost float, target int
    -> KMLPropertySetter
    -> KMLPropertySetter_2
KMLPropertySetter_2
    TESSELATE = Yes
    SUMMARY = <none>
    EXTRUDE = No
    GEOM_TYPE = Vector
    ADD_ATTR_TABLE = Yes
    NAME = @Value(NM_POLH)
    CONTENT = <img width="300" src="popup.png">
    ADDITIONAL_FILE_TABLE = /Users/andrewharvey/github/geo-demos/demos/iag/src/img/popup.png popup.png
    VISIBILITY = Yes
    CONTENT_TYPE = HTML
    -> Policies (writer OGCKML_1)
KMLPropertySetter [off]
    TESSELATE = Yes
    ATTR_TABLE_TITLE = Policy Details
    SUMMARY = <none>
    EXTRUDE = No
    GEOM_TYPE = Vector
    ADD_ATTR_TABLE = Yes
    NAME = @Value(NM_POLH)
    CONTENT:
      <link rel="stylesheet" href="/javascript/bootstrap/css/bootstrap.min.css">
      <link rel="stylesheet" href="/javascript/bootstrap/css/bootstrap-theme.min.css">
      <link rel="stylesheet" href="/javascript/fonts-font-awesome/css/font-awesome.min.css" />
      <link rel="stylesheet" href="css/app.css">
      <link rel="stylesheet" href="css/maps-googlestyle.css">

      <script src="/javascript/bootstrap/js/bootstrap.min.js"></script>

      <div class="">
          <header class="info-header {{type-class}}"><i class="fa fa-{{fa-type}}"></i> {{type}}</header>
          <div class="inner info-popup">
              <div class="row">
                  <div class="left-box info-box">
                      <span class="key">Building</span>
                      <br>
                      <span class="big-icon fa-stack fa-3x" style="font-size: 30px;">
                          <i class="info-icon fa fa-square fa-stack-2x {{building-color}}"></i>
                          <i class="info-icon fa fa-home fa-stack-1x fa-inverse"></i>
                      </span>
                      <br>
                      <p>
                      <!--<span class="box-label">Insured Sum:</span><br>-->
                      <span class="box-label insured-sum" rel="tooltip" style="cursor:pointer" data-toggle="tooltip" data-placement="right" title="Building Insured Sum">@Value(BuildingSumInsured)</span>
                          </p>
                      <p>
                          <span class="box-label">This Year Premium:</span><br>
                          <span class="box-label">@Value(ThisYearBldgPremium)</span>
                      </p>
                      <p>
                          <span class="box-label">Last 5 Years Premium:</span><br>
                          <span class="box-label">@Value(Last5YearsBldgPremium)</span>
                      </p>

                      <p>
                          <span class="box-label">Number of Terms:</span><br>
                          <span class="box-label">@Value(NumberBuildingsTerms)</span>
                      </p>

                      <p>
                          <span class="box-label">Recent Claim:</span><br>
                          <span class="box-label">@Value(RecentBuildingClaim) / @Value(RecentBuildingClaimCost)</span>
                      </p>
                  </div>
                  <div class="right-box info-box">
                      <span class="key">Contents</span>
                      <br>
                      <span class="big-icon fa-stack fa-3x" style="font-size: 30px;">
                          <i class="info-icon fa fa-square fa-stack-2x {{contents-color}}"></i>
                          <i class="info-icon fa fa-suitcase fa-stack-1x fa-inverse"></i>
                      </span>
                      <br>
                      <p>
                          <!--<span class="box-label">Insured Sum:</span><br>-->
                          <span class="box-label insured-sum" rel="tooltip" style="cursor:pointer" data-toggle="tooltip" data-placement="right" title="Contents Insured Sum">@Value(ContentsSumInsured)</span>
                      </p>

                      <p>
                          <span class="box-label">This Year Premium:</span><br>
                          <span class="box-label">@Value(ThisYearContPremium)</span>
                      </p>

                      <p>
                          <span class="box-label">Last 5 Years Premium:</span><br>
                          <span class="box-label">@Value(Last5YearsContPremium)</span>
                      </p>

                      <p>
                          <span class="box-label">Number of Terms:</span><br>
                          <span class="box-label">@Value(NumberContentsTerms)</span>
                      </p>

                      <p>
                          <span class="box-label">Recent Claim:</span><br>
                          <span class="box-label">@Value(RecentContentsClaim) / @Value(RecentContentsClaimCost)</span>
                      </p>
                  </div>
              </div>
              <div class="col-md-12">
                  <table class="table table-condensed table-striped">
                      <tbody>
                          <tr>
                              <td class="key">Year of Construction</td>
                              <td>@Value(YearOfConstruction)</td>
                          </tr>

                          <tr>
                              <td class="key">Number of Dwellings</td>
                              <td>@Value(Number_of_Dwellings)</td>
                          </tr>

                          <tr>
                              <td class="key">Size of Dwelling</td>
                              <td>@Value(SizeOfDwlling)</td>
                          </tr>

                          <tr>
                              <td class="key">Size of Garage</td>
                              <td>@Value(SizeOfGarage)</td>
                          </tr>

                          <tr>
                              <td class="key">Age of oldest policy holder</td>
                              <td>@Value(AgeOfOldestPolicyHolder)</td>
                          </tr>

                          <tr>
                              <td class="key">At risk of flood</td>
                              <td>@Value(AtRiskOfFlood)</td>
                          </tr>
                      </tbody>
                  </table>
              </div>
              <div class="subscribe">
                  <span><a href="#">More details</a></span>
              </div>
          </div>
      </div>
    ADDITIONAL_FILE_TABLE = /Users/andrewharvey/github/geo-demos/demos/iag/src/javascript/bootstrap/css/bootstrap.min.css /javascript/bootstrap/css/bootstrap.min.css /Users/andrewharvey/github/geo-demos/demos/iag/src/javascript/fonts-font-awesome/css/font-awesome.min.css /javascript/fonts-font-awesome/css/font-awesome.min.css /Users/andrewharvey/github/geo-demos/demos/iag/src/css/app.css css/app.css /Users/andrewharvey/github/geo-demos/resources/shared/maps-googlestyle.css css/maps-googlestyle.css /Users/andrewharvey/github/geo-demos/demos/iag/src/javascript/bootstrap/js/bootstrap.min.js /javascript/bootstrap/js/bootstrap.min.js
    VISIBILITY = Yes
    CONTENT_TYPE = HTML
    -> Policies (writer OGCKML_1)
Policies (writer OGCKML_1)
