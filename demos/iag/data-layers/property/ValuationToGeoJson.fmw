FME workspace ValuationToGeoJson.fmw

Parameters:
- SourceDataset_XLSXR = $(FME_MF_DIR)20140314 Google IAG Demo.xls   # Source Microsoft Excel File(s)
- SourceDataset_SHAPE = $(FME_MF_DIR)nz-primary-parcels/nz-primary-parcels-1.shp   # Source Esri Shape File(s)
- DestDataset_SHAPE = /Users/andrewharvey/github/geo-demos/demos/iag/data-layers/property   # Destination Esri Shape Directory

Readers:
- XLSXR_1: XLSXR from $(SourceDataset_XLSXR)
- SHAPE_1: SHAPE from $(SourceDataset_SHAPE)

Writers:
- SHAPE_2: SHAPE to $(DestDataset_SHAPE)

desc (reader XLSXR_1)
    attributes: Field char(21), Description char(58)
data (reader XLSXR_1)
    attributes: dipid char(15), parcel_id number(8,0), lat number(8,4), long number(8,4), val_ref char(13), property_type char(4), category char(35), full_address char(52), bedrooms number(2,0), bathrooms number(2,0), floor_area number(7,0), eyb_range number(5,0), cv number(8,0), lv number(8,0), iv number(9,0), val_date date, land_area number(6,0), improvement char(42), last_sale_agree date, last_sale_uncond date, last_sale_method char(21), last_sale_price number(8,0), title_no char(11), title_type char(12), legal_desc char(155), leasehold char(2), crosslease char(2), ttl_maori number(2,0), ttl_s28 number(2,0), ttl_s36 number(2,0),
      ttl_s54 number(2,0), ttl_eqc number(2,0), mortgage_lodged_date date, mortgage_lender char(4), last_consent date, last_consent_value number(7,0), avm_est number(8,0), avm_est_lo number(8,0), avm_est_hi number(8,0)
    -> FeatureMerger [input 2]
nz-primary-parcels-1 (reader SHAPE_1)
    attributes: id number(10,0), appellatio char(254), affected_s char(254), parcel_int char(100), topology_t char(100), statutory_ char(254), land_distr char(100), titles char(254), survey_are number(20,4), calc_area number(20,0)
    -> FeatureMerger [input 1]
FeatureMerger
    PROCESS_DUPS = No
    MERGE_TYPE = Attributes Only
    SUPPLIERS_FIRST = No
    JOIN_KEYS = @Value(id) @Value(parcel_id) AUTO
    SUPPLIER_PREFIX_DUMMY = YES
    NOT_MERGED -> StringFormatter
    MERGED -> StringFormatter
StringFormatter
    SRC_ATTRS = cv,lv,iv,avm_est,avm_est_lo,avm_est_hi
    FORMAT = %d
    -> ParcelValuations_BucklandsBeach (writer SHAPE_2)
ParcelValuations_BucklandsBeach (writer SHAPE_2)
    attributes: id char(200), appellatio char(200), affected_s char(200), parcel_int char(200), topology_t char(200), statutory_ char(200), land_distr char(200), titles char(200), survey_are char(200), calc_area char(200), dipid char(200), parcel_id char(200), lat char(200), long char(200), val_ref char(200), property_t char(200), category char(200), full_addre char(200), bedrooms char(200), bathrooms char(200), floor_area char(200), eyb_range char(200), cv char(200), lv char(200), iv char(200), val_date char(200), land_area char(200), improvemen char(200), last_sale_ char(200), last_sal00 char(200),
      last_sal01 char(200), last_sal02 char(200), title_no char(200), title_type char(200), legal_desc char(200), leasehold char(200), crosslease char(200), ttl_maori char(200), ttl_s28 char(200), ttl_s36 char(200), ttl_s54 char(200), ttl_eqc char(200), mortgage_l char(200), mortgage00 char(200), last_conse char(200), last_con00 char(200), avm_est char(200), avm_est_lo char(200), avm_est_hi char(200), numReferen char(200)
