FME workspace ValuationToJson.fmw

Parameters:
- SourceDataset_XLSXR = $(FME_MF_DIR)20140314 Google IAG Demo.xls   # Source Microsoft Excel File(s)
- DestDataset_JSON = $(FME_MF_DIR)valuation.json   # Destination JSON (JavaScript Object Notation) File
- DestDataset_TEXTLINE = $(FME_MF_DIR)valuation-object.json   # Destination Text File
- SourceDataset_SHAPE = $(FME_MF_DIR)nz-primary-parcels/nz-primary-parcels-1.shp   # Source Esri Shape File(s)

Readers:
- XLSXR_1: XLSXR from $(SourceDataset_XLSXR)
- SHAPE_1: SHAPE from $(SourceDataset_SHAPE)

Writers:
- JSON_1: JSON to $(DestDataset_JSON)
- TEXTLINE_1: TEXTLINE to $(DestDataset_TEXTLINE)

desc (reader XLSXR_1)
    attributes: Field char(21), Description char(58)
data (reader XLSXR_1)
    attributes: dipid char(15), parcel_id number(8,0), lat number(8,4), long number(8,4), val_ref char(13), property_type char(4), category char(35), full_address char(52), bedrooms number(2,0), bathrooms number(2,0), floor_area number(7,0), eyb_range number(5,0), cv number(8,0), lv number(8,0), iv number(9,0), val_date date, land_area number(6,0), improvement char(42), last_sale_agree date, last_sale_uncond date, last_sale_method char(21), last_sale_price number(8,0), title_no char(11), title_type char(12), legal_desc char(155), leasehold char(2), crosslease char(2), ttl_maori number(2,0), ttl_s28 number(2,0), ttl_s36 number(2,0),
      ttl_s54 number(2,0), ttl_eqc number(2,0), mortgage_lodged_date date, mortgage_lender char(4), last_consent date, last_consent_value number(7,0), avm_est number(8,0), avm_est_lo number(8,0), avm_est_hi number(8,0)
    -> valuation (writer JSON_1)
    -> Tester [off]
    -> FeatureMerger [input 2]
valuation (writer JSON_1) [off]
    attributes: dipid string, parcel_id float, loc.lat float, loc.long float, val_ref string, property_type string, category string, full_address string, bedrooms float, bathrooms float, floor_area float, eyb_range float, cv float, lv float, iv float, val_date string, land_area float, improvement string, last_sale_agree string, last_sale_uncond string, last_sale_method string, last_sale_price float, title_no string, title_type string, legal_desc string, leasehold string, crosslease string, ttl_maori float, ttl_s28 float, ttl_s36 float,
      ttl_s54 float, ttl_eqc float, mortgage_lodged_date string, mortgage_lender string, last_consent string, last_consent_value float, avm_est float, avm_est_lo float, avm_est_hi float
Tester
    TEST_MODE = Automatic
    TEST_DESCRIPTION = ""
    BOOL_OP = OR
    TEST_CLAUSE = TEST @Value(parcel_id) MATCHES_REGEX ^$
    FAILED -> JSONTemplater [input 2]
nz-primary-parcels-1 (reader SHAPE_1)
    attributes: id number(10,0), appellatio char(254), affected_s char(254), parcel_int char(100), topology_t char(100), statutory_ char(254), land_distr char(100), titles char(254), survey_are number(20,4), calc_area number(20,0)
    -> FeatureMerger [input 1]
FeatureMerger
    PROCESS_DUPS = No
    MERGE_TYPE = Attributes Only
    SUPPLIERS_FIRST = No
    JOIN_KEYS = @Value(id) @Value(parcel_id) AUTO
    SUPPLIER_PREFIX_DUMMY = YES
    REFERENCED -> JSONTemplater [input 2]
Creator
    NUM = 1
    GEOMTYPE = Geometry Object
    CREATED -> JSONTemplater [input 1]
JSONTemplater
    RESULT_ATTRIBUTE = text_line_data
    SUB_QUERY_EXPR:
      {
        "id": fme:get-attribute("parcel_id"),
        "data": {
              "bedrooms": fme:get-attribute("bedrooms"),
              "floor_area":  fme:get-attribute("floor_area"),
              "eyb_range": fme:get-attribute("eyb_range"),
              "cv": fme:get-attribute("cv"),
              "lv": fme:get-attribute("lv"),
              "iv": fme:get-attribute("iv"),
              "val_date": fme:get-attribute("val_date"),
              "land_area": fme:get-attribute("land_area"),
              "last_sale_agree": fme:get-attribute("last_sale_agree"),
              "last_sale_uncond": fme:get-attribute("last_sale_uncond"),
              "last_sale_method": fme:get-attribute("last_sale_method"),
              "last_sale_price": fme:get-attribute("last_sale_price")
        }
      }
    ROOT_QUERY_EXPR:
      [
      fme:process-features("SUB")
      ]
    VISIBLE_QUERY_VALIDATE = Yes
    -> text_line (writer TEXTLINE_1)
text_line (writer TEXTLINE_1)
    attributes: text_line_data buffer
